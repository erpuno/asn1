-- http://www.dsszzi.gov.ua/dsszzi/control/uk/publish/article?art_id=77726

-- https://zakon.rada.gov.ua/laws/show/z1401-12
-- https://zakon.rada.gov.ua/laws/show/z1402-12
-- https://zakon.rada.gov.ua/laws/show/z1398-12

-- PKCS + OCSP + TSP + Authentication + Information (X.501:08, X.509:08, X.511:08, X.520:08).

-- from: Наказ Міністерства юстиції України,
--   to: Адміністрації Державної служби спеціального зв’язку та захисту інформації України
-- date: 20.08.2012 #1236/5/453

KEP DEFINITIONS IMPLICIT TAGS ::=
BEGIN

IMPORTS Attribute, Name
  FROM  InformationFramework {joint-iso-itu-t ds(5) module(1) informationFramework(1) 3}
        AlgorithmIdentifier, AttributeCertificate, Certificate, CertificateList,
        CertificateSerialNumber, HASH{}, SIGNED{}, Extensions, Version
   FROM AuthenticationFramework {joint-iso-itu-t ds(5) module(1) authenticationFramework(7) 3}
        PolicyInformation, CRLReason
   FROM CertificateExtensions
        PKIStatusInfo
   FROM PKIXCMP-2009;

ContentInfo ::= SEQUENCE {
  contentType ContentType,
  content [0] EXPLICIT ANY DEFINED BY contentType }

UnknownInfo ::= NULL

CrlValidatedID ::= SEQUENCE {
  crlHash OtherHash,
  crlIdentifier CrlIdentifier OPTIONAL}

OtherHash ::= CHOICE {
  sha1Hash OtherHashValue,
  otherHash OtherHashAlgAndValue}

OcspListID ::= SEQUENCE {
  ocspResponses SEQUENCE OF OcspResponsesID}

OcspResponsesID ::= SEQUENCE {
  ocspIdentifier OcspIdentifier,
  ocspRepHash OtherHash OPTIONAL
}

OtherRevRefs ::= SEQUENCE {
  otherRevRefType OtherRevRefType,
  otherRevRefs ANY DEFINED BY otherRevRefType
}

OcspIdentifier ::= SEQUENCE {
  ocspResponderID ResponderID,
  producedAt GeneralizedTime
}


CMSVersion ::= INTEGER {v0(0), v1(1), v2(2), v3(3), v4(4), v5(5)}

gost34311 OBJECT IDENTIFIER ::= {iso(1) member-body(2) ua(804)
  root(2) security(1) cryptography(1) pki(1) pki-alg(1) pki-alg-hash (2) 1}

OTHER-NAME ::= TYPE-IDENTIFIER
GeneralNames ::= SEQUENCE SIZE (1..MAX) OF GeneralName
GeneralName ::= CHOICE {
  otherName                  [0]  INSTANCE OF OTHER-NAME,
  rfc822Name                 [1]  IA5String,
  dNSName                    [2]  IA5String,
  directoryName              [4]  Name,
  uniformResourceIdentifier  [6]  IA5String,
  iPAddress                  [7]  OCTET STRING,
  registeredID               [8]  OBJECT IDENTIFIER
}

TSAPolicyId ::= OBJECT IDENTIFIER
SignatureAlgorithmIdentifier ::= AlgorithmIdentifier
KeyIdentifier ::= OCTET STRING
SubjectKeyIdentifier ::= KeyIdentifier
RevocationInfoChoices ::= SET OF CertificateList
SignerInfos ::= SET OF SignerInfo
CertificateSet ::= SET OF Certificate
SignedData ::= SEQUENCE {
  version CMSVersion,
  digestAlgorithms DigestAlgorithmIdentifiers,
  encapContentInfo EncapsulatedContentInfo,
  certificates [0] IMPLICIT CertificateSet OPTIONAL,
  crls [1] IMPLICIT RevocationInfoChoices OPTIONAL,
  signerInfos SignerInfos }

EncapsulatedContentInfo ::= SEQUENCE {
  eContentType ContentType,
  eContent [0] EXPLICIT OCTET STRING OPTIONAL }

SignerInfo ::= SEQUENCE {
  version CMSVersion,
  sid SignerIdentifier,
  digestAlgorithm DigestAlgorithmIdentifier,
  signedAttrs [0] IMPLICIT SignedAttributes OPTIONAL,
  signatureAlgorithm SignatureAlgorithmIdentifier,
  signature OCTET STRING,
  unsignedAttrs [1] IMPLICIT UnsignedAttributes OPTIONAL }

SignerIdentifier ::= CHOICE {
  issuerAndSerialNumber IssuerAndSerialNumber,
  subjectKeyIdentifier [0] SubjectKeyIdentifier }

IssuerAndSerialNumber ::= SEQUENCE {
  issuer Name,
  serialNumber INTEGER }

Hash ::= OCTET STRING
  IssuerSerial ::= SEQUENCE {
  issuer GeneralNames,
  serialNumber CertificateSerialNumber}

ESSCertIDv2 ::= SEQUENCE {
  hashAlgorithm AlgorithmIdentifier,
  certHash Hash,
  issuerSerial IssuerSerial}

OtherHashValue ::= OCTET STRING
OtherHashAlgAndValue ::= SEQUENCE {
  hashAlgorithm AlgorithmIdentifier,
  hashVal OtherHashValue }

SPuri ::= IA5String

SigPolicyId ::= OBJECT IDENTIFIER
SigPolicyHash ::= OtherHashAlgAndValue
SigPolicyQualifierId ::= OBJECT IDENTIFIER

SignaturePolicyIdentifier ::= CHOICE {
  signaturePolicy SignaturePolicyId }

SigPolicyQualifierInfo ::= SEQUENCE {
  sigPolicyQualifierId SigPolicyQualifierId,
  sigQualifier ANY DEFINED BY sigPolicyQualifierId }

SignaturePolicyId ::= SEQUENCE {
  sigPolicyId SigPolicyId,
  sigPolicyHash SigPolicyHash OPTIONAL }

DigestAlgorithmIdentifiers ::= SET OF DigestAlgorithmIdentifier
DigestAlgorithmIdentifier ::= AlgorithmIdentifier
CertificateSerialNumber ::= INTEGER
SignedAttributes ::= SET SIZE (1..MAX) OF Attribute
UnsignedAttributes ::= SET SIZE (1..MAX) OF Attribute
Attribute ::= SEQUENCE {attrType OBJECT IDENTIFIER, attrValues SET OF AttributeValue }
AttributeValue ::= ANY
MessageDigest ::= OCTET STRING

   CertPolicyId ::= OBJECT IDENTIFIER

   PolicyQualifierInfo ::= SEQUENCE {
          policyQualifierId  OBJECT IDENTIFIER,
          qualifier          ANY OPTIONAL}

PolicyInformation ::= SEQUENCE {
  policyIdentifier  CertPolicyId,
  policyQualifiers  SEQUENCE SIZE (1..MAX) OF PolicyQualifierInfo OPTIONAL
}

SigningCertificateV2 ::= SEQUENCE {certs SEQUENCE OF ESSCertIDv2, policies SEQUENCE OF PolicyInformation OPTIONAL}
SignaturePolicyImplied ::= NULL

DisplayText ::= CHOICE {
  visibleString VisibleString (SIZE (1..200)),
  bmpString BMPString (SIZE (1..200)),
  utf8String UTF8String (SIZE (1..200))}

CrlOcspRef ::= SEQUENCE {
  crlids     [0] CRLListID OPTIONAL,
  ocspids    [1] OcspListID OPTIONAL,
  otherRev   [2] OtherRevRefs OPTIONAL }

CrlIdentifier ::= SEQUENCE {
  crlissuer Name,
  crlIssuedTime UTCTime,
  crlNumber INTEGER OPTIONAL }

BasicOCSPResponse ::= SEQUENCE {
  tbsResponseData ResponseData,
  signatureAlgorithm AlgorithmIdentifier,
  signature BIT STRING,
  certs [0] EXPLICIT SEQUENCE OF Certificate OPTIONAL}

ResponseData ::= SEQUENCE {
  version [0] EXPLICIT Version DEFAULT v1,
  responderID ResponderID,
  producedAt GeneralizedTime,
  responses SEQUENCE OF SingleResponse,
  responseExtensions [1] EXPLICIT Extensions OPTIONAL} 

ResponderID ::= CHOICE {
  byName [1] Name,
  byKey [2] KeyHash}

KeyHash ::= OCTET STRING

CertID ::= SEQUENCE {
  hashAlgorithm AlgorithmIdentifier,
  issuerNameHash OCTET STRING,
  issuerKeyHash OCTET STRING,
  serialNumber CertificateSerialNumber}

CertStatus ::= CHOICE {
  good [0] IMPLICIT NULL,
  revoked [1] IMPLICIT RevokedInfo,
  unknown [2] IMPLICIT UnknownInfo }

   CRLReason ::= ENUMERATED {
        unspecified             (0),
        keyCompromise           (1),
        cACompromise            (2),
        affiliationChanged      (3),
        superseded              (4),
        cessationOfOperation    (5),
        certificateHold         (6),
        removeFromCRL           (8),
        privilegeWithdrawn      (9),
        aACompromise           (10)
   }

RevokedInfo ::= SEQUENCE {
  revocationTime GeneralizedTime,
  revocationReason [0] EXPLICIT CRLReason OPTIONAL }

SingleResponse ::= SEQUENCE {
  certID CertID,
  certStatus CertStatus,
  thisUpdate GeneralizedTime,
  nextUpdate [0] EXPLICIT GeneralizedTime OPTIONAL,
  singleExtensions [1] EXPLICIT Extensions OPTIONAL }

CertificateList  ::=  SEQUENCE  {
     tbsCertList          TBSCertList,
     signatureAlgorithm   AlgorithmIdentifier,
     signature            BIT STRING  }

TBSCertList  ::=  SEQUENCE  {
     version                 Version OPTIONAL,
                                  -- if present, MUST be v2
     signature               AlgorithmIdentifier,
     issuer                  Name,
     thisUpdate              Time,
     nextUpdate              Time OPTIONAL,
     revokedCertificates     SEQUENCE OF SEQUENCE  {
          userCertificate         CertificateSerialNumber,
          revocationDate          Time,
          crlEntryExtensions      Extensions OPTIONAL
                                         -- if present, MUST be v2
                               }  OPTIONAL,
     crlExtensions           [0] Extensions OPTIONAL }
                                         -- if present, MUST be v2

RevocationValues ::= SEQUENCE {
  crlVals       [0] SEQUENCE OF CertificateList OPTIONAL,
  ocspVals      [1] SEQUENCE OF BasicOCSPResponse OPTIONAL,
  otherRevVals  [2] OtherRevVals OPTIONAL}

OtherRevValType ::= OBJECT IDENTIFIER
OtherRevVals ::= SEQUENCE { otherRevValType OtherRevValType }
CRLListID ::= SEQUENCE { crls SEQUENCE OF CrlValidatedID}

MessageImprint ::= SEQUENCE {
  hashAlgorithm AlgorithmIdentifier,
  hashedMessage OCTET STRING }

TimeStampReq ::= SEQUENCE {
  version           INTEGER { v1(1) },
  messageImprint    MessageImprint,
  reqPolicy         TSAPolicyId OPTIONAL,
  nonce             INTEGER OPTIONAL,
  certReq           BOOLEAN DEFAULT FALSE,
  extensions    [0] IMPLICIT Extensions OPTIONAL }

 PKIFreeText ::= SEQUENCE SIZE (1..MAX) OF UTF8String

 PKIStatus ::= INTEGER {
     accepted               (0),
     -- you got exactly what you asked for
     grantedWithMods        (1),
     -- you got something like what you asked for; the
     -- requester is responsible for ascertaining the differences
     rejection              (2),
     -- you don't get it, more information elsewhere in the message
     waiting                (3),
     -- the request body part has not yet been processed; expect to
     -- hear more later (note: proper handling of this status
     -- response MAY use the polling req/rep PKIMessages specified
     -- in Section 5.3.22; alternatively, polling in the underlying
     -- transport layer MAY have some utility in this regard)
     revocationWarning      (4),
     -- this message contains a warning that a revocation is
     -- imminent
     revocationNotification (5),
     -- notification that a revocation has occurred
     keyUpdateWarning       (6)
     -- update already done for the oldCertId specified in
     -- CertReqMsg
 }

 PKIFailureInfo ::= BIT STRING {
 -- since we can fail in more than one way!
 -- More codes may be added in the future if/when required.
     badAlg              (0),
     -- unrecognized or unsupported Algorithm Identifier
     badMessageCheck     (1),
     -- integrity check failed (e.g., signature did not verify)
     badRequest          (2),
     -- transaction not permitted or supported
     badTime             (3),
     -- messageTime was not sufficiently close to the system time,
     -- as defined by local policy
     badCertId           (4),
     -- no certificate could be found matching the provided criteria
     badDataFormat       (5),
     -- the data submitted has the wrong format
     wrongAuthority      (6),
     -- the authority indicated in the request is different from the
     -- one creating the response token
     incorrectData       (7),
     -- the requester's data is incorrect (for notary services)
     missingTimeStamp    (8),
     -- when the timestamp is missing but should be there
     -- (by policy)
     badPOP              (9),
     -- the proof-of-possession failed
     certRevoked         (10),
     -- the certificate has already been revoked
     certConfirmed       (11),
     -- the certificate has already been confirmed
     wrongIntegrity      (12),
     -- invalid integrity, password based instead of signature or
     -- vice versa
     badRecipientNonce   (13),
     -- invalid recipient nonce, either missing or wrong value
     timeNotAvailable    (14),
     -- the TSA's time source is not available
     unacceptedPolicy    (15),
     -- the requested TSA policy is not supported by the TSA
     unacceptedExtension (16),
     -- the requested extension is not supported by the TSA
     addInfoNotAvailable (17),
     -- the additional information requested could not be
     -- understood or is not available
     badSenderNonce      (18),
     -- invalid sender nonce, either missing or wrong size
     badCertTemplate     (19),
     -- invalid cert. template or missing mandatory information
     signerNotTrusted    (20),
     -- signer of the message unknown or not trusted
     transactionIdInUse  (21),
     -- the transaction identifier is already in use
     unsupportedVersion  (22),
     -- the version of the message is not supported
     notAuthorized       (23),
     -- the sender was not authorized to make the preceding
     -- request or perform the preceding action
     systemUnavail       (24),
     -- the request cannot be handled due to system unavailability
     systemFailure       (25),
     -- the request cannot be handled due to system failure
     duplicateCertReq    (26)
     -- certificate cannot be issued because a duplicate
     -- certificate already exists
 }

PKIStatusInfo ::= SEQUENCE {
     status        PKIStatus,
     statusString  PKIFreeText     OPTIONAL,
     failInfo      PKIFailureInfo  OPTIONAL }

TimeStampResp ::= SEQUENCE {
  status PKIStatusInfo,
  timeStampToken TimeStampToken OPTIONAL }

TimeStampToken ::= ContentInfo

TSTInfo ::= SEQUENCE {
  version INTEGER { v1(1)},
  policy TSAPolicyId,
  messageImprint MessageImprint,
  serialNumber INTEGER,
  genTime GeneralizedTime,
  accuracy Accuracy OPTIONAL,
  nonce INTEGER OPTIONAL,
  tsa [0] GeneralName OPTIONAL,
  extensions [1] IMPLICIT Extensions OPTIONAL }

Accuracy ::= SEQUENCE {
    seconds     INTEGER          OPTIONAL,
    millis  [0] INTEGER (1..999) OPTIONAL,
    micros  [1] INTEGER (1..999) OPTIONAL  }

OtherRevRefType  ::= OBJECT IDENTIFIER
ContentType      ::= OBJECT IDENTIFIER
id-data          OBJECT IDENTIFIER ::= {1 2 840 113549 1 7 1}
id-signedData    OBJECT IDENTIFIER ::= {1 2 840 113549 1 7 2}
id-contentType   OBJECT IDENTIFIER ::= {1 2 840 113549 1 9 3}
id-messageDigest OBJECT IDENTIFIER ::= {1 2 840 113549 1 9 4}
id-signingTime   OBJECT IDENTIFIER ::= {1 2 840 113549 1 9 5}

id-aa-signTSToken OBJECT IDENTIFIER        ::= {1 2 840 113549 1 9 16 id-aa(2) 14}
id-aa-ets-sigPolicyId OBJECT IDENTIFIER    ::= {1 2 840 113549 1 9 16 id-aa(2) 15}
id-aa-ets-ContentTS OBJECT IDENTIFIER      ::= {1 2 840 113549 1 9 16 id-aa(2) 20}
id-aa-ets-certRefs OBJECT IDENTIFIER       ::= {1 2 840 113549 1 9 16 id-aa(2) 21}
id-aa-ets-revocationRefs OBJECT IDENTIFIER ::= {1 2 840 113549 1 9 16 id-aa(2) 22}
id-aa-ets-certValues OBJECT IDENTIFIER     ::= {1 2 840 113549 1 9 16 id-aa(2) 23}
id-aa-ets-revoValues OBJECT IDENTIFIER     ::= {1 2 840 113549 1 9 16 id-aa(2) 24}
id-aa-signingCertV2 OBJECT IDENTIFIER      ::= {1 2 840 113549 1 9 16 id-aa(2) 47}
id-spq-ets-uri OBJECT IDENTIFIER           ::= {1 2 840 113549 1 9 16 id-spq(5) 1}
id-spq-ets-unotice OBJECT IDENTIFIER       ::= {1 2 840 113549 1 9 16 id-spq(5) 2}

dstu7564-256 OBJECT IDENTIFIER ::= {iso(1) member-body(2) ukraine(804) root(2) security(1) cryptography(1) pki(1) alg(1) hash(2) dstu7564(2) 1}
dstu7564-384 OBJECT IDENTIFIER ::= {iso(1) member-body(2) ukraine(804) root(2) security(1) cryptography(1) pki(1) alg(1) hash(2) dstu7564(2) 2}
dstu7564-512 OBJECT IDENTIFIER ::= {iso(1) member-body(2) ukraine(804) root(2) security(1) cryptography(1) pki(1) alg(1) hash(2) dstu7564(2) 3}

id-kp-timeStamping OBJECT IDENTIFIER ::= {iso(1) identified-organization(3) dod(6) internet(1) security(5) mechanisms(5) pkix(7) id-kp(3) 8}
id-ct-TSTInfo OBJECT IDENTIFIER      ::= {iso(1) member-body(2) us(840) rsadsi(113549) pkcs(1) pkcs-9(9) smime(16) ct(1)4}

END
