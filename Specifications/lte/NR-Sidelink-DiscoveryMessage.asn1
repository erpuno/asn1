-- This file was generated by the Objective Systems ASN1C Compiler
-- (http://www.obj-sys.com).  Version: 7.9.1, Date: 25-Jul-2025.

NR-Sidelink-DiscoveryMessage DEFINITIONS AUTOMATIC TAGS ::= BEGIN

IMPORTS

CellAccessRelatedInfo, SL-ServingCellInfo-r17, SL-RelayIndicationMP-r18
FROM NR-RRC-Definitions ;

-- Productions

SL-AccessInfo-L2U2N-r17 ::= SEQUENCE {
   cellAccessRelatedInfo-r17 [0] CellAccessRelatedInfo,
   sl-ServingCellInfo-r17 [1] SL-ServingCellInfo-r17,
   ...,
   [[
      sl-RelayIndication-r18 [2] SL-RelayIndicationMP-r18 OPTIONAL
   ]]
}

END
