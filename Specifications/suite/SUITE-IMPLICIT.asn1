SUITE-IMPLICIT DEFINITIONS IMPLICIT TAGS ::= BEGIN

  Real ::= SEQUENCE {
    mantissa INTEGER,
    base INTEGER (2|10),
    exponent INTEGER
  }

  AtomicOpt ::= SET {
    int INTEGER,
    octetSet [1] SET OF OCTET STRING,
    octetOpt OCTET STRING OPTIONAL,
    octetSetOpt [2] SET OF OCTET STRING OPTIONAL,
    boolOpt BOOLEAN OPTIONAL,
    real Real
  }

  ImpExpProd ::= SEQUENCE {
    intSetImp [1] IMPLICIT SET OF INTEGER (0..7),
    intSetExp [2] EXPLICIT SET OF INTEGER (0..7),
    intImp [3] IMPLICIT INTEGER (0..7),
    intExp [4] EXPLICIT INTEGER (0..7),
    boolImp [5] IMPLICIT BOOLEAN,
    boolExp [6] EXPLICIT BOOLEAN,
    intSetImpOpt [7] IMPLICIT SET OF INTEGER (0..7) OPTIONAL,
    intSetExpOpt [8] EXPLICIT SET OF INTEGER (0..7) OPTIONAL,
    intImpOpt [9] IMPLICIT INTEGER (0..7) OPTIONAL,
    intExpOpt [10] EXPLICIT INTEGER (0..7) OPTIONAL,
    realSetImp [11] IMPLICIT SET OF Real,
    realSetExp [12] EXPLICIT SET OF Real
  }

  ImpExpSum ::= CHOICE {
    intSetImp [1] IMPLICIT SET OF INTEGER (0..7),
    intSetExp [2] EXPLICIT SET OF INTEGER (0..7),
    intImp [3] IMPLICIT INTEGER (0..7),
    intExp [4] EXPLICIT INTEGER (0..7),
    boolImp [5] IMPLICIT BOOLEAN,
    boolExp [6] EXPLICIT BOOLEAN,
    realSetImp [7] IMPLICIT SET OF Real,
    realSetExp [8] EXPLICIT SET OF Real
  }

  NoTagsTagsMix ::= SEQUENCE {
    intSet1 SET OF INTEGER (0..7),
    intSet2 SET OF INTEGER (0..7),
    seqSet1 SEQUENCE OF INTEGER (0..7),
    seqSet2 SEQUENCE OF INTEGER (0..7),
    int1 INTEGER (0..7),
    int2 INTEGER (0..7),
    bool1 BOOLEAN,
    bool2 BOOLEAN,
    intSetOpt1 [1] SET OF INTEGER (0..7) OPTIONAL,
    intSetOpt2 [2] SET OF INTEGER (0..7) OPTIONAL,
    intOpt1 [3] INTEGER (0..7) OPTIONAL,
    intOpt2 [4] INTEGER (0..7) OPTIONAL
  }

  Versioning ::= INTEGER { v1(0) }

-- > 'SUITE-IMPLICIT':decode('List',<<48,4,4,0,5,0>>).
-- {ok,{'List',<<>>,{'end','NULL'}}}

  List ::= SEQUENCE {
    data OCTET STRING,
    next CHOICE { list List, end NULL }
  }

-- > 'SUITE-IMPLICIT':decode('Tensor',<<48,9,49,7,48,5,48,3,2,1,1>>).
-- {ok,{'Tensor',[[[1]]]}}

  Tensor ::= SEQUENCE {
    body SET OF
         SEQUENCE OF
         SEQUENCE OF INTEGER
  }

-- > 'SUITE-IMPLICIT':decode('ListOrTensorRaw',<<161,4,4,0,5,0>>).
-- {ok,{list,{'List',<<>>,{'end','NULL'}}}}

  ListOrTensorRaw ::= CHOICE {
    list [1] List,
    tensor [2] Tensor,
    int  [3] INTEGER,
    oct  [4] OCTET STRING,
    bool [5] BOOLEAN
  }

  ListOrTensorTags ::= CHOICE {
    list1 [1] List,
    list2 [2] IMPLICIT List,
    list3 [3] EXPLICIT List,
    tensor1 [4] Tensor,
    tensor2 [5] IMPLICIT Tensor,
    tensor3 [6] EXPLICIT Tensor,
    int  [7] INTEGER,
    oct  [8] OCTET STRING,
    bool [9] BOOLEAN
  }

-- > 'SUITE-IMPLICIT':encode('Msg',{protocolOp,{seq,{'Seq',{oct,"3"}}}}).
-- {ok,<<48,5,96,3,129,1,51>>}

  Msg ::= SEQUENCE { protocolOp CHOICE { seq Seq } }
  Seq ::= [APPLICATION 0] SEQUENCE { listOrTensor ListOrTensorApp }
  ListOrTensorApp ::= CHOICE {
    int  [1] INTEGER,
    oct  [2] OCTET STRING,
    bool [3] BOOLEAN,
    ts   [4] TeletexString,
    us   [5] UniversalString,
    ias  [6] IA5String,
    vs   [7] VisibleString,
    utf8 [8] UTF8String,
    ps   [9] PrintableString,
    ns   [10] NumericString,
    bpm  [11] BMPString,
    bs   [12] BIT STRING,
    io   [13] OBJECT IDENTIFIER,
    tensor [100] Tensor,
    list   [101] List,
    ...
  }

END
