-- Module MSGeneralAutoActionTypes (X.413:06/1999)
-- See also ITU-T X.413 (06/1999)
-- See also the index of all ASN.1 assignments needed in this document

MSGeneralAutoActionTypes {joint-iso-itu-t mhs(6) ms(4) modules(0)
  general-auto-action-types(3) version-1994(0)} DEFINITIONS ::=
BEGIN

-- Prologue
-- Exports everything
IMPORTS
  -- AUTO-ACTION and AUTO-ACTION-ERROR information object classes
  AUTO-ACTION,
    AUTO-ACTION-ERROR,
    -- MS abstract-service data-types and abstract-errors
    EntryClass, EntryInformationSelection, EntryModification, Filter,
    message-group-error, modify-error, service-error, SequenceNumber
    --==
    FROM MSAbstractService {joint-iso-itu-t mhs(6) ms(4) modules(0)
      abstract-service(1) version-1999(1)}
  -- MS Object Identifiers
  id-aae-auto-alert-error, id-act-auto-alert, id-act-auto-correlate-reports,
    id-act-auto-delete, id-act-auto-modify
    --==
    FROM MSObjectIdentifiers {joint-iso-itu-t mhs(6) ms(4) modules(0)
      object-identifiers(0) version-1999(1)}
  -- MS abstract-service upper bounds
  ub-alert-addresses, ub-modifications, ub-supplementary-info-length
    --==
    FROM MSUpperBounds {joint-iso-itu-t mhs(6) ms(4) modules(0) upper-bounds(4)
      version-1994(0)}
  -- MTS abstract-service
  security-error
    --==
    FROM MTSAbstractService {joint-iso-itu-t mhs(6) mts(3) modules(0)
      mts-abstract-service(1) version-1999(1)};

-- Auto-action table information object set
AutoActionTable AUTO-ACTION ::=
  {GeneralAutoActions | ContentSpecificAutoActions}

GeneralAutoActions AUTO-ACTION ::=
  {auto-alert, ... -- 1994 extension additions --, auto-modify |
   auto-correlate-reports | auto-delete}

ContentSpecificAutoActions AUTO-ACTION ::=
  {...}

-- Auto-action error table information object set
AutoActionErrorTable AUTO-ACTION-ERROR ::=
  {GeneralAutoActionErrors | ContentSpecificAutoActionErrors}

GeneralAutoActionErrors AUTO-ACTION-ERROR ::=
  {auto-alert-error | modify-error | service-error | security-error |
   message-group-error, ... -- For future extension additions --}

ContentSpecificAutoActionErrors AUTO-ACTION-ERROR ::=
  {...}

-- Auto-action-types
auto-alert AUTO-ACTION ::= {
  REGISTRATION PARAMETER IS  AutoAlertRegistrationParameter
  ERRORS                     {auto-alert-error}
  IDENTIFIED BY              id-act-auto-alert
}

AutoAlertRegistrationParameter ::= SET {
  filter                       [0]  Filter OPTIONAL,
  alert-destinations
    [1]  SEQUENCE SIZE (1..ub-alert-addresses) OF AlertDestination OPTIONAL,
  requested-attributes         [2]  EntryInformationSelection OPTIONAL,
  -- 1994 extension 
  suppress-alert-destinations  [3]  BOOLEAN DEFAULT TRUE
}

AlertDestination ::= SEQUENCE {
  alert-address    EXTERNAL,
  alert-qualifier  OCTET STRING OPTIONAL
}

--
auto-modify AUTO-ACTION ::= {
  REGISTRATION PARAMETER IS  AutoModifyRegistrationParameter
  ERRORS
    {security-error | service-error | modify-error | message-group-error}
  IDENTIFIED BY              id-act-auto-modify
}

AutoModifyRegistrationParameter ::= SET {
  entry-class    [0]  EntryClass DEFAULT delivery,
  filter         [1]  Filter OPTIONAL,
  modifications  [2]  SEQUENCE SIZE (1..ub-modifications) OF EntryModification
}

--
auto-correlate-reports AUTO-ACTION ::= {
  IDENTIFIED BY  id-act-auto-correlate-reports
}

--
auto-delete AUTO-ACTION ::= {
  ERRORS         {security-error}
  IDENTIFIED BY  id-act-auto-delete
}

-- Auto-action errors
auto-alert-error AUTO-ACTION-ERROR ::= {
  PARAMETER  SEQUENCE SIZE (1..ub-alert-addresses) OF AutoAlertErrorIndication
  CODE       global:id-aae-auto-alert-error
}

AutoAlertErrorIndication ::= SET {
  failing-alert-destination  [0]  AlertDestination OPTIONAL,
  supplementary-information
    [1]  GeneralString(SIZE (1..ub-supplementary-info-length)) OPTIONAL
}

END -- of MSGeneralAutoActionTypes

-- Generated by Asnp, the ASN.1 pretty-printer of France Telecom R&D
